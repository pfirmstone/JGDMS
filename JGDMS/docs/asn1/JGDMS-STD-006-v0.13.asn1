-- JGDMS-STD-006-v0.13.asn1
--
-- Consolidated, COMPILING ASN.1 module for JGDMS-STD-006 — ATOMIC DER Wire Format —
-- v0.13-DRAFT. "ATOMIC DER" is the FORMAT's proper name (it names the @AtomicSerial
-- object model it encodes); "JGDMS-STD-006" remains the STANDARD document identifier;
-- generic "DER" below means X.690 DER (the encoding rules), unchanged.
-- Assembled from the asn1-fenced snippets in:
--   JGDMS/docs/JGDMS-STD-006-DER-WireFormat-v0.13-DRAFT.md  (sections 3.12, 4.3, 4.5, 7.1-7.8)
--
-- This file is a VALIDATION ARTIFACT for open item 20 ("validate every ASN.1 module
-- against a real ASN.1 compiler"). It is not itself normative; see the accompanying
-- JGDMS-STD-006-v0.13-validation.md for the classified list of every deviation between
-- this compiling module and the spec prose, and for the proposed spec wording changes
-- (NOT applied here; the spec source is untouched).
--
-- Compiled and round-trip-tested with Python asn1tools 0.167.0, the 'der' codec.
--
-- G8 SYNC PASS (2026-07-24): brought up to date with ratified prose+code on three
-- fronts (see JGDMS-STD-006-v0.13-validation.md, "2026-07-24 sync" section):
--   1. Chain ceilings + chain-integrity constraints (spec section 4.5 table +
--      section 7.8 "Chain integrity and ceilings" block): maxChainRecords /
--      maxChainBytes added; completeness + adjacent-pair cross-check comments at
--      the section 7.8 productions.
--   2. Throwable ceilings (RATIFIED Peter 2026-07-24, open item 21, commit
--      9dcb74342): maxCauseDepth 64 -> 12; maxSuppressedPerNode / maxThrowableNodes
--      added; ThrowableRecord.suppressed re-bounded; DerThrowableForm realization
--      note added.
--   3. Appendix C stream layer (RATIFIED 2026-07-21; NORMATIVE, MANDATORY part of
--      the standard per the spec header's Integral-parts declaration; T2-built):
--      new clearly-delimited STREAM LAYER section at the end of the module
--      (StreamFormatVersion, SchemaChainRef, DedupMarshalledInstanceRecord,
--      DedupNestedAtomicRecord, maxDistinctChainsPerStream, maxDedupTableBytes).
--
-- VALIDATION FINDING (type-model-pinning pass, 2026-07-05): the section 3.12
-- AnyElement CHOICE's collection arms (canonicalCollection/orderedCollection)
-- wrap CanonicalCollection/OrderedCollection, which are themselves CHOICEs over
-- the three canonicalise (or three ordered) productions. CanonicalSet and
-- CanonicalMultiset are structurally IDENTICAL ASN.1 productions (both
-- SET SIZE(0..maxCollection) OF Element), so a naive untagged CHOICE between
-- them is not tag-distinguishable per X.680 section 30.6. Confirmed
-- empirically: an untagged CanonicalCollection encoded the 'set' and 'bag' arms
-- to byte-identical octets, and asn1tools 0.167.0 hung (did not error) decoding
-- it. Fixed by giving CanonicalCollection/OrderedCollection their own inner
-- [0]/[1]/[2] IMPLICIT context tags (legal: SET OF/SEQUENCE OF are not
-- themselves CHOICE/ANY types, so X.680 section 31.2.7 does not block IMPLICIT
-- here), matching the ReducingDomainRecord pattern already in this module. This
-- is exactly the failure mode section 3.12/4.3 fence (d) (canonical minimal tag
-- encoding + deterministic value-to-category mapping) exists to prevent, and it
-- was caught by the round-trip test this pass required, not by the compiler
-- alone (the module still parsed without the inner tags; only decode hung).
-- Verified after the fix: set/bag encode to different octets
-- (be08a006040101040102 vs be08a106040101040102) and both round-trip correctly;
-- a reserved-gap tag ([10]-[19]/[21]-[29]) and an out-of-range tag (>[31])
-- both correctly hard-reject as CHOICE decode errors (fence (c)), confirming
-- the "automatic in the CHOICE form" claim in the design memo.
--
-- ============================================================================
-- TAGGING MODE DECISION
-- ============================================================================
-- DEFINITIONS EXPLICIT TAGS is used, per spec section 4.6 (added in the
-- review addendum, 2026-07-04): every context tag this standard defines is
-- additionally written IMPLICIT explicitly at its use site, so the module
-- default governs only future untagged additions.
--
-- The ReducingDomainRecord CHOICE arms (section 7.2) are the one place where
-- this module previously differed from the spec: the original spec prose left
-- them bare `[0]`/`[1]`/`[2]` (no EXPLICIT/IMPLICIT qualifier), which under
-- DEFINITIONS EXPLICIT TAGS wraps each arm in an extra constructed tag,
-- different bytes from IMPLICIT. Section 4.6 fixed the spec to mark all three
-- arms IMPLICIT (legal: NULL/SEQUENCE types, not CHOICE/ANY themselves, so
-- X.680 section 31.2.7's restriction does not apply), and this module now
-- matches (nullCs/digest/url all `[n] IMPLICIT`). This was a genuine
-- byte-on-the-wire difference, not a stylistic one; both TAGS modes do NOT
-- produce identical bytes for this type once a bare `[n]` tag is involved.
--
-- EXPLICIT TAGS remains the chosen module default because:
--   1. It keeps the underlying UNIVERSAL tag visible under every context tag,
--      which is one fewer thing a non-JVM decoder can get wrong when a field
--      is added later and a spec editor forgets to write IMPLICIT.
--   2. X.680 section 31.2.7 forbids IMPLICIT tagging of a CHOICE or ANY
--      alternative unless that alternative itself carries an explicit tag.
--      Every CHOICE in this module (ReducingDomainRecord, ProxyDescriptor)
--      tags each arm explicitly, foreclosing that hazard. EntryFieldValue
--      (section 7.7.2) is the one CHOICE left untagged, matching the spec
--      exactly; see the byte-equality note at its definition below.
-- ============================================================================

-- Module OID under the Zeus Project Services Pty Ltd arc:
--   enterprise(1) 999999   = the company PEN (PLACEHOLDER — replace on IANA assignment)
--     jgdms(1) atomicDer(1) v13(13)
-- (999999 is a documented placeholder so the module compiles; see spec section 4.4.)
JGDMS-STD-006
{ iso(1) identified-organization(3) dod(6) internet(1) private(4)
  enterprise(1) 999999 jgdms(1) atomicDer(1) v13(13) }
DEFINITIONS
EXPLICIT TAGS ::=
BEGIN

-- ============================================================================
-- Section 4.5 Profile size ceilings (value assignments)
--
-- SPEC-DEFECT: the spec table (section 4.5) spells these MAX-FIELDS,
-- MAX-COLLECTION, MAX-STACK-FRAMES, MAX-CAUSE-DEPTH, MAX-GROUPS,
-- MAX-KNOWN-SERVICE-IDS, MAX-OPERATIONS, MAX-PARAMETERS, MAX-INTERFACES; all
-- upper-case-leading identifiers. ASN.1 (X.680 section 12.3) requires a
-- valuereference to begin with a lower-case letter; an upper-case-leading
-- identifier is parsed as a typereference, and standalone `MAX` besides is a
-- reserved word inside a SIZE/value-range constraint (X.680 section 51.6, the
-- "MAX" keyword denoting the upper end of a PermittedAlphabet/SIZE range).
-- `SIZE(0..MAX-FIELDS)` is therefore not merely non-conformant style, it fails
-- to parse as a value reference at all under a strict grammar (and some tools
-- may mis-parse it as `SIZE(0..MAX)` followed by a dangling `-FIELDS`).
-- Renamed here to lower-camelCase value references, per the recommended
-- spelling in the validation report.
-- ============================================================================

maxFields            INTEGER ::= 65535
maxCollection        INTEGER ::= 65536
maxStackFrames       INTEGER ::= 2048   -- RATIFIED (Peter, 2026-07-24, item 21)
-- maxCauseDepth 64 -> 12: RATIFIED (Peter, 2026-07-24, item 21; was proposed 64).
-- Under the nested-@AtomicSerial carrier realization (DerThrowableForm) each cause
-- level consumes one codec nesting level and MAX_NESTING=16 makes 64 structurally
-- unreachable; a consistency test pins maxCauseDepth + 2 <= MAX_NESTING. Capture
-- truncates with an explicit marker (boundary class + message preserved); decode
-- rejects over-ceiling wire fail-secure. (Spec section 4.5 table.)
maxCauseDepth        INTEGER ::= 12
-- RATIFIED (Peter, 2026-07-24, item 21): per-node suppressed[] count. NOTE: the
-- spec's section 7.6 asn1 snippet still writes SIZE(0..maxCollection) on
-- `suppressed` — intra-spec drift against the ratified section 4.5 table row
-- ("ThrowableRecord.suppressed per node" = 32); this module follows the RATIFIED
-- section 4.5 value. Flagged in the validation report (2026-07-24 sync).
maxSuppressedPerNode INTEGER ::= 32
-- RATIFIED (Peter, 2026-07-24, item 21): total ThrowableRecord nodes per carried
-- fault tree (root + all cause/suppressed descendants). A GLOBAL count over the
-- recursion — not expressible as a per-field SIZE constraint; enforced by the
-- decoder's node counter, metered during decode. Carrier className additionally
-- bounded 1..2048 octets (section 4.5 table note; the bound lives in the
-- DerThrowableForm carrier realization, not this hand-authored SEQUENCE).
maxThrowableNodes    INTEGER ::= 128
maxGroups            INTEGER ::= 128
maxKnownServiceIds   INTEGER ::= 256
maxOperations        INTEGER ::= 1024
maxParameters        INTEGER ::= 255
maxInterfaces        INTEGER ::= 64

-- Section 4.5 chain ceilings (T6 base adoption; section 7.8 "Chain integrity and
-- ceilings" block). NOTE ON STATUS MARKERS: the spec's section 4.5 table currently
-- annotates these two rows "[PROPOSED]" while the identical values are RATIFIED
-- for the stream layer (Appendix C section C.8, Peter 2026-07-21) and the section
-- 7.8 integrity block is marked NORMATIVE — the residual [PROPOSED] marker
-- appears to be stale; flagged in the validation report rather than silently
-- resolved here. Both are INCLUSIVE bounds, metered DURING the chain-decode loop
-- (the ceiling-breaching record is the last one parsed), at EVERY chain decode
-- site: the top-level MarshalledInstanceRecord.schemaBytes and each nested
-- @AtomicSerial field record's embedded chain.
maxChainRecords      INTEGER ::= 64      -- records per encoded chain (65 rejected)
maxChainBytes        INTEGER ::= 65536   -- cumulative encoded bytes per chain (65537 rejected)

-- Section 7.2 named ceilings (established pattern predating section 4.5's
-- table; same SPEC-DEFECT class. MAX_DOMAINS / MAX_CERTS / MAX_DIGEST_LEN /
-- MAX_CERT_LEN use underscore-separated upper-case names in prose, not
-- valuereferences at all in the original snippets (they were comments, not
-- ASN.1). Given proper value-assignment status here for the SIZE constraints
-- that use them.

maxDomains    INTEGER ::= 4096
maxCerts      INTEGER ::= 100
maxDigestLen  INTEGER ::= 512
maxCertLen    INTEGER ::= 65536
-- Section 7.3 DigestCodeSourceRecord.certificates shares maxCerts/maxCertLen
-- with the section 7.2 UrlCodeSourceRecord certificate path; the spec's
-- MAX_CERT_COUNT/MAX_CERT_BYTES names (section 7.3) were the same logical
-- bound under a different name and are merged here into maxCerts/maxCertLen
-- (spec section 4.5, review addendum).

-- ============================================================================
-- Section 4.3 AlgorithmIdentifier (RFC 5280, imported conceptually "from X.509")
--
-- SPEC-GAP: the spec says AlgorithmIdentifier is "reused... the X.509
-- structure" but never states a normative import source (module name + OID
-- for a machine-readable IMPORT). Defined locally here per RFC 5280 section
-- 4.1.1.2. `parameters ANY OPTIONAL` (1988/1990 ASN.1 `ANY`) is accepted by
-- asn1tools (see validation report), so no OCTET-STRING STUB substitution was
-- needed in practice.
-- ============================================================================

AlgorithmIdentifier ::= SEQUENCE {
    algorithm   OBJECT IDENTIFIER,
    parameters  ANY OPTIONAL
}

-- ============================================================================
-- Section 4.4 Top-level type discriminator (RATIFIED 2026-07-06: OID-rooted)
--
-- Each top-level wire object is wrapped so a decoder selects its schema from a
-- single explicit OBJECT IDENTIFIER (board H3: one discriminator, not two). The
-- body is opaque OCTET STRING content the envelope never re-encodes (same
-- discipline as SignedObject.tbs, section 7.4.1).
--
-- OID ROOT: registrant = Zeus Project Services Pty Ltd (the legal company); one
-- IANA PEN roots all its projects, JGDMS is a sub-arc, ATOMIC DER a sub-arc of
-- JGDMS, and TypedWireObject typeIds live under ...atomicDer.wireTypes:
--     1.3.6.1.4.1.<PEN>   Zeus Project Services Pty Ltd  (PEN, PLACEHOLDER)
--             .1  jgdms  .1  atomicDer  .1  wireTypes
-- <PEN> (written 999999) is a documented PLACEHOLDER; Zeus Project Services Pty
-- Ltd will register an IANA Private Enterprise Number and it MUST be replaced
-- before v1.0 (spec section 4.4).
-- ============================================================================

zeusProjectServices OBJECT IDENTIFIER ::=
  { iso(1) identified-organization(3) dod(6) internet(1) private(4)
    enterprise(1) 999999 }   -- PLACEHOLDER PEN — replace on IANA assignment
jgdms       OBJECT IDENTIFIER ::= { zeusProjectServices 1 }
atomicDer   OBJECT IDENTIFIER ::= { jgdms 1 }
wireTypes   OBJECT IDENTIFIER ::= { atomicDer 1 }   -- TypedWireObject type-ID subtree

-- Example wire-type typeId allocations under ...atomicDer.wireTypes:
--   marshalledInstance    { wireTypes 1 }
--   unicastResponse       { wireTypes 2 }
--   accessControlContext  { wireTypes 3 }

TypedWireObject ::= SEQUENCE {
    typeId  OBJECT IDENTIFIER,   -- a child of wireTypes (...atomicDer.wireTypes.n)
    body    OCTET STRING
}

-- ============================================================================
-- Section 7.1 Identity: UserSubjectBlock and Principal
-- ============================================================================

Principal ::= SEQUENCE {
    className   UTF8String,
    name        UTF8String
}

UserSubject ::= SEQUENCE {
    -- ORDER-SIGNIFICANT (section 3.8): the principal sequence order is intrinsic.
    principals  SEQUENCE (SIZE(0..64)) OF Principal
}

UserSubjectBlock ::= SEQUENCE {
    -- ORDER-SIGNIFICANT (section 3.8): outermost-first; subjects[0] is the primary user.
    subjects    SEQUENCE (SIZE(0..16)) OF UserSubject
}

-- ============================================================================
-- Section 7.2 Authorization: AccessControlContext and reducing domains
-- ============================================================================

-- Codebase identity of one reducing domain. NO principals, NO permissions.
-- Arms are IMPLICIT (spec section 4.6): legal here because NULL/SEQUENCE are not
-- CHOICE or ANY types themselves (X.680 section 31.2.7 forbids IMPLICIT tagging
-- of a CHOICE/ANY alternative without an explicit tag; not the case here).
ReducingDomainRecord ::= CHOICE {
    nullCs      [0] IMPLICIT NULL,
    digest      [1] IMPLICIT DigestCodeSourceRecord,
    url         [2] IMPLICIT UrlCodeSourceRecord
}

UrlCodeSourceRecord ::= SEQUENCE {
    locationUri     UTF8String,
    certificates    SEQUENCE (SIZE(0..maxCerts)) OF OCTET STRING (SIZE(1..maxCertLen)) OPTIONAL
}

AccessControlContextRecord ::= SEQUENCE {
    -- ORDER-SIGNIFICANT (section 3.8): captured domain order is preserved end to end.
    domains     SEQUENCE (SIZE(0..maxDomains)) OF ReducingDomainRecord
}

DigestValue ::= SEQUENCE {
    algorithm   AlgorithmIdentifier,
    digest      OCTET STRING (SIZE(1..maxDigestLen))
}

-- ============================================================================
-- Section 7.3 Code Identity: DigestCodeSourceRecord
-- ============================================================================

-- The DigestCodeSource `unverified` boolean (source accessor unverified())
-- deliberately does NOT travel: it is transient in the class and absent here.
-- The verified/unverified state is the receiver's LOCAL determination and MUST
-- NOT be trusted from the wire; a decoded DigestCodeSource is UNVERIFIED
-- (unverified == true) until the receiver verifies it locally, and only when the
-- code is present or being loaded anyway (never download-to-verify). See spec
-- section 7.3.1 (Verification policy, RATIFIED 2026-07-06).
DigestCodeSourceRecord ::= SEQUENCE {
    locationUri     UTF8String,
    -- [0] IMPLICIT context tag (section 4.5 distinct-tag rule): untagged, this
    -- SEQUENCE OF would collide with the DigestValue SEQUENCE that follows
    -- (both tag 0x30). maxCerts/maxCertLen shared with the section 7.2
    -- UrlCodeSourceRecord certificate path; same logical bound (section 4.5).
    certificates    [0] IMPLICIT SEQUENCE (SIZE(0..maxCerts)) OF OCTET STRING (SIZE(1..maxCertLen)) OPTIONAL,
    digest          DigestValue
    -- NB: no `verified`/`unverified` field (see comment above). The record is a
    -- digest CLAIM only.
}

-- ============================================================================
-- Section 7.4 SCAP Data Objects; illustrative skeletons ([OPEN] in spec)
-- ============================================================================

-- Field lists RESOLVED (2026-07-06) against the @AtomicSerial classes in
-- au.net.zeus.jgdms.api.codebase (jgdms-platform). Authority-classified safe as
-- structured DER: signature-verified (JarAnalysisReport/RegistryVerdict/CrashReport)
-- or content-hash self-verified (AnalysisRequest); see spec section 7.4.

AnalysisRequest ::= SEQUENCE {
    packedJarBytes  OCTET STRING,
    contentHash     DigestValue,
    originalUri     UTF8String,
    maxBfsDepth     INTEGER (0..MAX)
    -- bare MAX as sole upper bound is legal ASN.1 (X.680 section 51.6).
}

-- ClassAnalysisResult: STUB (field list not yet extracted from the @AtomicSerial
-- class; spec section 7.4 [PROPOSED]). Opaque per-record DER for now.
ClassAnalysisResult ::= OCTET STRING

JarAnalysisReport ::= SEQUENCE {
    contentHash          DigestValue,
    classNames           SEQUENCE (SIZE(0..maxCollection)) OF UTF8String,
    classResults         SEQUENCE (SIZE(0..maxCollection)) OF ClassAnalysisResult,
    engineSignature      OCTET STRING,
    declaredPermissions  SEQUENCE (SIZE(0..maxCollection)) OF UTF8String,
    codebaseUrls         SEQUENCE (SIZE(0..maxCollection)) OF UTF8String
}

RegistryVerdict ::= SEQUENCE {
    codebaseUrls  SEQUENCE (SIZE(0..maxCollection)) OF UTF8String,
    verdict       INTEGER,
    timestamp     INTEGER,
    signature     OCTET STRING
}

CrashReport ::= SEQUENCE {
    codebaseUrls   SEQUENCE (SIZE(0..maxCollection)) OF UTF8String,
    exitCode       INTEGER,
    incarnation    INTEGER,
    stderrSummary  UTF8String,
    signature      OCTET STRING
}

-- Generic signed-object form (available; the as-built SCAP classes carry their
-- signature inline instead, see spec section 7.4).
SignedObject ::= SEQUENCE {
    tbs         OCTET STRING,
    signature   SEQUENCE {
        algorithm   AlgorithmIdentifier,
        value       OCTET STRING
    }
}

-- ============================================================================
-- Section 7.6 Substituted Standard Types
-- ============================================================================

-- ILLUSTRATIVE: `Element` (and the `key`/`value` positions in the map types) is
-- an intentional placeholder for a per-element DER encoding. Stubbed here as
-- OCTET STRING (opaque per-element DER, consistent with EntryFieldValue's
-- `present OCTET STRING` pattern, section 7.7.2) so the module compiles; the
-- real element wire-type is carried in the schema token (set:/bag:/map:/...) not
-- the ASN.1 type. A concrete collection field substitutes its element type.
Element ::= OCTET STRING

-- Section 7.6 / 3.8 collection field types, one per ordering discipline. The
-- discipline is fixed by the declared Java type at schema-generation time and
-- baked into the schema wire-type token; the ASN.1 container type below pins the
-- wire TAG that goes with each token (built codec, branch der-collection-codec):
--
--   CANONICALISE (non-deterministic-order Set/Map) -> SET OF, UNIVERSAL tag 0x31.
--     A SET OF is octet-sorted per X.690 section 11.6; a conformant DER decoder
--     rejects an out-of-order SET OF, giving the section 11.6 ascending-order
--     guarantee at the type layer (Option A).
--       set:  -> CanonicalSet      (octet-sorted, distinct elements)
--       bag:  -> CanonicalMultiset (octet-sorted, duplicates permitted)
--       map:  -> CanonicalMap      (SET OF SEQUENCE{key,value}; entries octet-sorted
--                                   by the encoded KEY, per-entry SEQUENCE tag 0x30)
--   PRESERVE (deterministic-order List/Deque/LinkedHash*/Sorted*/Enum*/... ) ->
--     SEQUENCE OF, UNIVERSAL tag 0x30, iteration order emitted verbatim.
--       orderedset: -> OrderedSetField   (order kept, distinct elements)
--       list:       -> ListField         (order kept, duplicates permitted)
--       orderedmap: -> OrderedMapField    (SEQUENCE OF SEQUENCE{key,value}, both 0x30)
--
-- SIZE(0..maxCollection) is inclusive: the codec accepts exactly maxCollection
-- (65536) elements/entries and rejects maxCollection+1 (section 4.5).

CanonicalSet      ::= SET      (SIZE(0..maxCollection)) OF Element
CanonicalMultiset ::= SET      (SIZE(0..maxCollection)) OF Element
CanonicalMap      ::= SET      (SIZE(0..maxCollection)) OF SEQUENCE { key Element, value Element }

OrderedSetField   ::= SEQUENCE (SIZE(0..maxCollection)) OF Element
ListField         ::= SEQUENCE (SIZE(0..maxCollection)) OF Element
OrderedMapField   ::= SEQUENCE (SIZE(0..maxCollection)) OF SEQUENCE { key Element, value Element }

-- ============================================================================
-- Section 3.12 Wire Type Model: the Any self-describing element CHOICE
--
-- AnyElement is the rule-selected fallback wire form for a collection element
-- whose declared generic type is unresolvable at the declaration site (a raw
-- collection, an unbounded/lower-bounded wildcard, an Object element, or a
-- type variable in a generic AtomicSerial class; section 3.12). It is a
-- context-tagged CHOICE, not a SEQUENCE with a tag field and a body field:
-- the CHOICE's own context tag IS the category discriminator, so there is no
-- second field that can disagree with the payload's real category.
--
-- ILLUSTRATIVE: AtomicSerialRecord is stubbed as OCTET STRING (opaque
-- per-record DER), matching the Element stub above; the real AtomicSerial
-- record shape (a SEQUENCE for most records, a proxy-record form, or NULL for
-- a stateless record; section 3.9/3.10) is class-specific and
-- schema-digest-identified, not a single ASN.1 production. CanonicalCollection
-- and OrderedCollection are CHOICEs over the three canonicalise / three
-- preserve productions already defined above (section 7.6); the Any form's
-- collection arms accept any of the six collection tokens, discriminated at
-- that inner level by each production's own outer tag (0x31 for the three
-- SET OF, 0x30 for the three SEQUENCE OF), which the EXPLICIT wrapping below
-- preserves.
AtomicSerialRecord ::= OCTET STRING

-- CanonicalCollection / OrderedCollection arms carry their own inner context
-- tags ([0]-[2] IMPLICIT). This is required, not stylistic: CanonicalSet and
-- CanonicalMultiset are structurally identical ASN.1 productions (both
-- SET SIZE(0..maxCollection) OF Element), so an untagged CHOICE between them
-- is not tag-distinguishable (X.680 section 30.6 CHOICE distinct-tag rule) and
-- the two arms would encode to byte-identical octets, breaking fence (d)'s
-- deterministic value-to-category mapping (section 3.12/4.3). IMPLICIT is
-- legal here (unlike on the AnyElement arms below): SET OF / SEQUENCE OF are
-- not themselves CHOICE or ANY types, so X.680 section 31.2.7's restriction on
-- IMPLICIT-tagging a CHOICE/ANY alternative does not apply, the same
-- reasoning as ReducingDomainRecord's IMPLICIT arms above (section 4.6).
-- The Any registry's own [30]/[31] EXPLICIT tags (below) still preserve the
-- 0x31/0x30 SET OF/SEQUENCE OF outer tag one level up, as section 3.12 states;
-- this inner tag is the additional, ASN.1-mandatory disambiguation between the
-- three canonicalise (or three ordered) collection tokens sharing that outer tag.
CanonicalCollection ::= CHOICE {
    set  [0] IMPLICIT CanonicalSet,
    bag  [1] IMPLICIT CanonicalMultiset,
    map  [2] IMPLICIT CanonicalMap
}

OrderedCollection ::= CHOICE {
    orderedset  [0] IMPLICIT OrderedSetField,
    list        [1] IMPLICIT ListField,
    orderedmap  [2] IMPLICIT OrderedMapField
}

-- Scalar arms [0]-[9] are IMPLICIT: a cross-language reader determines the
-- primitive category from the context tag alone, and the value bytes past the
-- tag are the scalar's ordinary canonical DER (no wrapper). The
-- atomicSerialObject/canonicalCollection/orderedCollection arms are EXPLICIT
-- because each payload's own outer tag is load-bearing (the record's own tag,
-- section 3.9/3.10; the SET OF 0x31 / SEQUENCE OF 0x30 preserve-vs-canonicalise
-- discriminator, section 3.8/7.6), and IMPLICIT would overwrite it in place:
-- X.680 section 31.2.7 forbids IMPLICIT-tagging a CHOICE/ANY alternative whose
-- own outer tag carries meaning. Gaps [10]-[19]/[21]-[29] are RESERVED (section
-- 3.12/4.5 Any tag registry); a tag outside this CHOICE's listed alternatives
-- is an unregistered tag, and a conformant decoder hard-rejects it (fence (c),
-- section 3.12/4.3; in the CHOICE form this is automatic, since an unlisted
-- alternative is itself a CHOICE decode error).
AnyElement ::= CHOICE {
    scalarBoolean        [0]  IMPLICIT BOOLEAN,
    scalarByte           [1]  IMPLICIT INTEGER,
    scalarShort          [2]  IMPLICIT INTEGER,
    scalarInt            [3]  IMPLICIT INTEGER,
    scalarLong           [4]  IMPLICIT INTEGER,
    scalarFloat          [5]  IMPLICIT OCTET STRING,
    scalarDouble         [6]  IMPLICIT OCTET STRING,
    scalarChar           [7]  IMPLICIT INTEGER,
    scalarString         [8]  IMPLICIT UTF8String,
    scalarBytes          [9]  IMPLICIT OCTET STRING,
    atomicSerialObject   [20] EXPLICIT AtomicSerialRecord,
    canonicalCollection  [30] EXPLICIT CanonicalCollection,
    orderedCollection    [31] EXPLICIT OrderedCollection
}

StackTraceElement ::= SEQUENCE {
    declaringClass  UTF8String,
    methodName      UTF8String,
    fileName        UTF8String OPTIONAL,
    lineNumber      INTEGER
}

-- SAFE SUBSET (RATIFIED 2026-07-06, spec section 7.6): only inert data travels
-- (class NAME string, message, bounded stack, nested records). NO `clazz` Class,
-- NO `perm` Permission, NO classname/length/eof; reflective-constructor
-- reconstruction is EXCLUDED (gadget-adjacent). See spec section 7.6 Throwable note.
--
-- [0]/[1] IMPLICIT context tags on suppressed/cause: both are OPTIONAL and both
-- would otherwise carry universal tag 0x30 (suppressed = SEQUENCE OF ...,
-- cause = a ThrowableRecord SEQUENCE), so untagged they violate the X.680
-- distinct-tag rule (section 4.5); they are indistinguishable when only one is
-- present.
-- Ceilings RATIFIED (Peter, 2026-07-24, open item 21 CLOSED): maxStackFrames=2048,
-- maxCauseDepth=12, maxSuppressedPerNode=32, maxThrowableNodes=128 (section 4.5).
--
-- REALIZATION NOTE (2026-07-24, post-review; spec section 7.6): the
-- invocation-layer fault carrier (org.apache.river.api.io.DerThrowableForm,
-- applied at the AtomicDerInvocationDispatcher.marshalThrow/unmarshalThrow seam)
-- realizes this RATIFIED field set (className/message/stackTrace/suppressed/cause;
-- the five gadget-adjacent fields excluded) in @AtomicSerial SCHEMA-RECORD FRAMING
-- rather than this hand-authored SEQUENCE — the closed DER registry continues to
-- defer Throwable itself. The decoder never resolves the carried class name; typed
-- rebuild happens only at the trusted client seam. This SEQUENCE remains the
-- normative field-set/bounds statement the carrier realizes.
ThrowableRecord ::= SEQUENCE {
    className     UTF8String,            -- class NAME only (not a Class object)
    message       UTF8String OPTIONAL,
    -- ORDER-SIGNIFICANT (section 3.8): stack frames are top-of-stack first
    stackTrace    SEQUENCE (SIZE(0..maxStackFrames)) OF StackTraceElement,
    -- suppressed per-node count bound is maxSuppressedPerNode (RATIFIED section
    -- 4.5), NOT maxCollection — see the intra-spec-drift note at the
    -- maxSuppressedPerNode value assignment above.
    suppressed    [0] IMPLICIT SEQUENCE (SIZE(0..maxSuppressedPerNode)) OF ThrowableRecord OPTIONAL,
    cause         [1] IMPLICIT ThrowableRecord OPTIONAL
    -- suppressed[] and cause nest ThrowableRecords; cause-chain depth <=
    -- maxCauseDepth (12; maxCauseDepth + 2 <= MAX_NESTING=16 consistency
    -- constraint); TOTAL nodes per fault tree <= maxThrowableNodes (128, a global
    -- decoder-metered count, not a SIZE constraint); acyclic (section 3.7/3.12).
    -- Capture truncates at the ceilings with an explicit marker; decode rejects
    -- over-ceiling wire fail-secure.
}

-- Section 7.6 Permission: NOT a structured DER wire type.
-- RATIFIED (Peter, 2026-07-06): a java.security.Permission likely need not
-- travel the wire at all; IF it does, it is carried as its TEXTUAL string form
-- and RE-PARSED on decode through the trusted policy parser, NEVER
-- reconstituted from serialized object state (authority-forgery / gadget
-- vector; consistent with the 2026-06 PermissionSerializer deletion). The
-- earlier structured Permission SEQUENCE (className, name, actions) form is
-- WITHDRAWN. When a textual Permission is carried it is simply a
-- PermissionTextForm UTF8String (see below); there is no per-field DER record.
PermissionTextForm ::= UTF8String
    -- the exact policy grammar the trusted parser accepts (a permission grant
    -- line: class name plus optional target and actions). The receiver
    -- reconstructs authority ONLY by parsing this through the vetted parser
    -- (section 7.6); it is never built from decoded per-field state.

-- Section 7.5 PermissionGrant / DigestGrant: likewise NOT structured DER.
-- RATIFIED (Peter, 2026-07-06): grants are authority-bearing objects that
-- (in-tree) deliberately do NOT implement Serializable and use the
-- Serialization Builder Pattern (PermissionGrant.java). On the wire they
-- travel as their TEXTUAL policy-grant form (STD-004 policy syntax) and are
-- RE-PARSED through the trusted policy parser, never directly deserialized
-- from wire-controlled fields. See section 7.5.
PermissionGrantTextForm ::= UTF8String
    -- the STD-004 textual policy-grant form; reconstructed ONLY via the vetted
    -- policy parser (section 7.5).

-- ============================================================================
-- Section 7.7.1 Entry Schema Identity
-- ============================================================================

EntryWireFieldDef ::= SEQUENCE {
    wireName  UTF8String (SIZE(1..255)),
    wireType  UTF8String (SIZE(1..1024))
}

EntrySchemaRecord ::= SEQUENCE {
    className       UTF8String (SIZE(1..1024)),
    -- superclassHash absent when direct superclass is Object.
    superclassHash  OCTET STRING (SIZE(32)) OPTIONAL,
    -- ORDER-SIGNIFICANT (section 3.8): field[i] corresponds to fieldValues[i] in EntryRecord.
    fields          SEQUENCE (SIZE(1..maxFields)) OF EntryWireFieldDef
}

-- ============================================================================
-- Section 7.7.2 Entry Instances
-- ============================================================================

-- Reverted to the spec's untagged CHOICE (byte-equality-matching-critical per
-- section 7.7.2: EntryRecord template matching relies on this exact encoding).
-- The untagged form is valid ASN.1; the alternatives are already distinguished
-- by their own tags, NULL vs OCTET STRING (X.680 section 30.6 distinct-tag rule
-- for CHOICE arms is satisfied without added context tags).
EntryFieldValue ::= CHOICE {
    absent  NULL,
    present OCTET STRING
}

EntryRecord ::= SEQUENCE {
    hashAlgorithm   INTEGER (1..255),
    schemaHash      OCTET STRING (SIZE(32)),
    -- ORDER-SIGNIFICANT (section 3.8): fieldValues[i] corresponds to fields[i]
    fieldValues     SEQUENCE (SIZE(1..maxFields)) OF EntryFieldValue
}

-- ============================================================================
-- Section 7.7.3 Service Identity
-- ============================================================================

ServiceID ::= OCTET STRING (SIZE(16))

-- ============================================================================
-- Section 7.7.4 Proxy Descriptor
-- ============================================================================

JeriEndpointRecord ::= SEQUENCE {
    spiffeId    UTF8String (SIZE(1..2048)),
    host        UTF8String (SIZE(1..253)),
    port        INTEGER (1..65535),
    tlsRequired BOOLEAN
}

TypeDescriptor ::= SEQUENCE {
    typeName  UTF8String (SIZE(1..1024)),
    nullable  BOOLEAN
}

OperationDescriptor ::= SEQUENCE {
    name        UTF8String (SIZE(1..255)),
    -- ORDER-SIGNIFICANT (section 3.8): parameter order is part of the method signature.
    parameters  SEQUENCE (SIZE(0..maxParameters)) OF TypeDescriptor,
    returnType  TypeDescriptor
}

ServiceSpecRecord ::= SEQUENCE {
    interfaceName  UTF8String (SIZE(1..1024)),
    -- ORDER-SIGNIFICANT (section 3.8): operation order determines generated interface layout.
    operations     SEQUENCE (SIZE(1..maxOperations)) OF OperationDescriptor,
    protocol       UTF8String (SIZE(1..255)),
    endpoint       UTF8String (SIZE(1..2048))
}

ProxyDescriptor ::= CHOICE {
    jeriEndpoint  [0] IMPLICIT JeriEndpointRecord,
    serviceSpec   [1] IMPLICIT ServiceSpecRecord
}

-- ============================================================================
-- Section 7.7.5 ServiceItem and ServiceTemplate
-- ============================================================================

ServiceItemRecord ::= SEQUENCE {
    serviceId   ServiceID,
    attributes  SEQUENCE (SIZE(0..64)) OF EntryRecord,
    proxy       ProxyDescriptor
}

EntryTemplate ::= SEQUENCE {
    hashAlgorithm INTEGER (1..255),
    schemaHash    OCTET STRING (SIZE(32)),
    -- ORDER-SIGNIFICANT (section 3.8): fieldValues[i] matches fields[i].
    fieldValues   SEQUENCE (SIZE(1..maxFields)) OF EntryFieldValue
}

-- Context tags per section 4.5 distinct-tag rule: requiredInterfaces and
-- attributeTemplates are both SEQUENCE OF (tag 0x30) and both OPTIONAL;
-- untagged they are indistinguishable when only one is present.
ServiceTemplateRecord ::= SEQUENCE {
    serviceId           [0] IMPLICIT ServiceID OPTIONAL,
    requiredInterfaces  [1] IMPLICIT SEQUENCE (SIZE(0..maxInterfaces)) OF OCTET STRING (SIZE(32)) OPTIONAL,
    attributeTemplates  [2] IMPLICIT SEQUENCE (SIZE(0..64)) OF EntryTemplate OPTIONAL
}

-- ============================================================================
-- Section 7.7.6 Lease Records
-- ============================================================================

-- Named values, matching net.jini.core.lease.Lease exactly:
--   Lease.FOREVER = Long.MAX_VALUE : "never expires" / "request forever"
--   Lease.ANY     = -1             : "any duration the grantor chooses is acceptable"
leaseForever INTEGER ::= 9223372036854775807
leaseAny     INTEGER ::= -1

LeaseRecord ::= SEQUENCE {
    leaseId     OCTET STRING (SIZE(16)),
    grantorId   ServiceID,
    -- Absolute expiry in epoch-millis.  leaseForever = no expiry.
    expiry      INTEGER,
    renewable   BOOLEAN
}

LeaseRenewalRecord ::= SEQUENCE {
    leaseId           OCTET STRING (SIZE(16)),
    requestedDuration INTEGER
}

LeaseCancellationRecord ::= SEQUENCE {
    leaseId OCTET STRING (SIZE(16))
}

-- ============================================================================
-- Section 7.7.7 Multicast Discovery Wire Types
-- ============================================================================

-- Multicast announcement: sent periodically by a Registrar on UDP port 4160.
MulticastAnnouncementRecord ::= SEQUENCE {
    sequenceNumber  INTEGER,
    host            UTF8String (SIZE(1..253)),
    port            INTEGER (1..65535),
    -- ORDER-SIGNIFICANT (section 3.8): group membership order is preserved
    groups          SEQUENCE (SIZE(0..maxGroups)) OF UTF8String,
    serviceId       ServiceID,
    signerPrincipal UTF8String,
    -- [0] IMPLICIT context tag (section 4.5): untagged, an absent signerCert
    -- makes the signature OCTET STRING indistinguishable from it.
    signerCert      [0] IMPLICIT OCTET STRING OPTIONAL,
    signature       OCTET STRING
}

-- Multicast request: sent by a client seeking Registrars.
MulticastRequestRecord ::= SEQUENCE {
    host            UTF8String (SIZE(1..253)),
    port            INTEGER (1..65535),
    -- ORDER-SIGNIFICANT (section 3.8)
    groups          SEQUENCE (SIZE(0..maxGroups)) OF UTF8String,
    -- ORDER-SIGNIFICANT (section 3.8): ServiceIDs already known to the client.
    knownServiceIds SEQUENCE (SIZE(0..maxKnownServiceIds)) OF ServiceID,
    signerPrincipal UTF8String,
    signerCert      [0] IMPLICIT OCTET STRING OPTIONAL,
    signature       OCTET STRING
}

-- TBS (to-be-signed) content (NORMATIVE in spec prose).
--
-- The spec's original single illustrative `MulticastTbs` type (whose last
-- field was a prose ellipsis, not concrete ASN.1) has been concretised in the
-- spec (section 7.7.7, review addendum 2026-07-04) into the two types below:
-- one per distinct wire record (announcement vs request), each listing its
-- record's actual preceding fields verbatim. This module matches the spec.

MulticastAnnouncementTbs ::= SEQUENCE {
    formatName      UTF8String,
    protocolVersion INTEGER,
    sequenceNumber  INTEGER,
    host            UTF8String (SIZE(1..253)),
    port            INTEGER (1..65535),
    groups          SEQUENCE (SIZE(0..maxGroups)) OF UTF8String,
    serviceId       ServiceID,
    signerPrincipal UTF8String,
    signerCert      [0] IMPLICIT OCTET STRING OPTIONAL
    -- signature is NOT included here: it is the value computed over this TBS.
}

MulticastRequestTbs ::= SEQUENCE {
    formatName      UTF8String,
    protocolVersion INTEGER,
    host            UTF8String (SIZE(1..253)),
    port            INTEGER (1..65535),
    groups          SEQUENCE (SIZE(0..maxGroups)) OF UTF8String,
    knownServiceIds SEQUENCE (SIZE(0..maxKnownServiceIds)) OF ServiceID,
    signerPrincipal UTF8String,
    signerCert      [0] IMPLICIT OCTET STRING OPTIONAL
}

-- ============================================================================
-- Section 7.7.8 Unicast Discovery Response
-- ============================================================================

UnicastResponseRecord ::= SEQUENCE {
    host        UTF8String (SIZE(1..253)),
    port        INTEGER (1..65535),
    -- ORDER-SIGNIFICANT (section 3.8): group membership order preserved
    groups      SEQUENCE (SIZE(0..maxGroups)) OF UTF8String,
    serviceId   ServiceID,
    proxy       ProxyDescriptor
}

-- ============================================================================
-- Section 7.8 MarshalledInstance
-- ============================================================================

AtomicSerialFieldDef ::= SEQUENCE {
    wireName  UTF8String (SIZE(1..255)),
    wireType  UTF8String (SIZE(1..1024))
}

AtomicSerialSchemaRecord ::= SEQUENCE {
    className        UTF8String (SIZE(1..1024)),
    -- SHA-256(DER(parent AtomicSerialSchemaRecord)); absent when parent is Object
    parentSchemaHash OCTET STRING (SIZE(32)) OPTIONAL,
    -- ORDER-SIGNIFICANT (section 3.8): field[i] corresponds to payload position i
    fields           SEQUENCE (SIZE(0..maxFields)) OF AtomicSerialFieldDef
}

-- CHAIN INTEGRITY AND CEILINGS (NORMATIVE; spec section 7.8 "Chain integrity and
-- ceilings" block, added under T6 chain-ceiling adoption). schemaBytes (below) and
-- every nested @AtomicSerial field record's embedded chain carry a leaf-first
-- concatenation of AtomicSerialSchemaRecord DER SEQUENCEs. These constraints are
-- semantic rules over that concatenation and are NOT expressible as per-field
-- ASN.1 constraints; they apply identically at EVERY chain decode site (top-level
-- P1 MarshalledInstanceRecord and nested P2 records alike), as hard decode
-- rejects (fail-secure, principle 6) — never a skip, default, or fallback:
--   * COMPLETENESS: the terminal (last, root) record MUST NOT carry a
--     parentSchemaHash. A terminal record with a dangling parentSchemaHash is a
--     TRUNCATED CHAIN and MUST be rejected. (Without this, truncated {leaf} and
--     full {leaf, parent, root} yield the same leaf digest from different bytes,
--     breaking the injectivity of schemaDigest over chain bytes.)
--   * ADJACENT-PAIR MERKLE CROSS-CHECK: each record's parentSchemaHash MUST equal
--     the next record's schema version digest (SHA-256 of that record's DER), and
--     every NON-terminal record MUST carry one.
--   * CEILINGS: maxChainRecords (64) records and maxChainBytes (65536) cumulative
--     bytes per chain, inclusive, metered DURING the chain-decode loop.

MarshalledInstanceRecord ::= SEQUENCE {
    payloadBytes       OCTET STRING,
    schemaBytes        OCTET STRING,
    schemaDigest       OCTET STRING (SIZE(32)),
    payloadFormat      UTF8String
}

-- ============================================================================
-- ============================================================================
-- STREAM LAYER — Appendix C, Stream Schema Dedup
--   (JGDMS-STD-006-Appendix-C-Stream-Schema-Dedup-v0.1-DRAFT.md, internal
--   version 0.3-DRAFT)
--
-- NORMATIVE and MANDATORY: per the spec header's Integral-parts declaration and
-- Peter's 2026-07-21 ratification, dedup is the SOLE stream form of the released
-- DER object-stream format — not a negotiated mode. One record sequence, one
-- stream encoding (G1 at the stream layer). The record-level canonical forms
-- above (MarshalledInstanceRecord, and the nested SEQUENCE{schemaChainBytes,
-- payloadBytes} form of STD-008 section 16) remain defined and in use for MI
-- state, persistence, [8] proxy interiors, and as reconstitution targets — they
-- are NOT stream productions (Appendix C sections C.5.3/C.5.4). Everything in
-- this section applies to DER OBJECT STREAMS only; the standalone
-- MarshalledInstance capture path never uses these productions (section C.1.2).
-- ============================================================================
-- ============================================================================

-- Stream ceilings (Appendix C section C.8.1; RATIFIED Peter 2026-07-21).
-- Per-stream dedup-table bounds, inclusive, metered DURING decode at each
-- fullChain table insertion (the stream is rejected at the first violating
-- site). maxChainRecords/maxChainBytes above bound each individual chain at
-- every site — ONE profile, stream and record-level alike (section C.8.1).
maxDistinctChainsPerStream INTEGER ::= 256      -- distinct chain identities per stream table
maxDedupTableBytes         INTEGER ::= 1048576  -- sum of stored chain bytes per stream table

-- The stream-format version octet (Appendix C section C.5.2; [PROPOSED], the one
-- v0.3 item awaiting ratification — repurposed per the 2026-07-21 ruling from
-- the superseded v0.2 mode marker). MANDATORY first TLV of every stream, exactly
-- once: wire bytes 8F 01 01 for version 1 (this appendix). A stream not
-- beginning with it, a duplicate, a content length != 1, or an unknown version
-- octet is a hard reject; there is no unversioned form. Tag [15] is the next
-- free object-stream item tag after [0]-[14] (STD-008 section 15.2/15.2.1;
-- registration there pending, Appendix C section C.13.3 item 2).
StreamFormatVersion ::= [15] IMPLICIT OCTET STRING (SIZE(1))

streamFormatVersion1 StreamFormatVersion ::= '01'H

-- SchemaChainRef (Appendix C section C.5.1; RATIFIED). The stream-layer carrier
-- of a schema chain: the PINNED first-full-then-reference rule (section C.6.1,
-- no encoder discretion) selects the arm — first occurrence of a chain identity
-- in the stream's normative traversal order (section C.6.2, record-entry
-- pre-order: a record's own chain site precedes every site in its payload) MUST
-- be fullChain; every subsequent occurrence MUST be chainRef. Decoders MUST
-- reject a chainRef whose digest is not already tabled (unknown-digest reject,
-- never a fetch or fallback) AND a fullChain whose identity is already tabled
-- (duplicate-full reject — the mandatory-dedup enforcement, section C.9.2).
-- The chain identity is SHA-256 over the RECEIVED leaf-record bytes (strict
-- canonical DER enforced within fullChain content; section C.7.3), and the
-- fullChain content is subject to the full chain-integrity block above
-- (completeness, Merkle cross-check, maxChainRecords/maxChainBytes).
-- Both arms IMPLICIT over OCTET STRING (a primitive, non-CHOICE type; X.680
-- section 31.2.7 does not bite): tag bytes 0x80 (fullChain) / 0x81 (chainRef).
SchemaChainRef ::= CHOICE {
    fullChain [0] IMPLICIT OCTET STRING (SIZE(1..maxChainBytes)),
    chainRef  [1] IMPLICIT OCTET STRING (SIZE(32))
}

-- Stream form of the P1 record (Appendix C section C.5.3; RATIFIED): replaces
-- MarshalledInstanceRecord at P1 STREAM sites ([1] CTX_ATOMIC items). Exactly
-- three fields — schemaDigest is DELIBERATELY ABSENT (derivable in both arms:
-- computed from fullChain bytes / the chainRef IS the digest; removing it makes
-- a lying digest unrepresentable). payloadFormat unchanged
-- ("JGDMS-STD-006/ATOMIC-DER"). Reconstitution rebuilds the canonical four-field
-- record byte-for-byte, inserting the computed leaf digest (round-trip law,
-- section C.5.4). NOT used inside [8] proxy interiors, which carry the canonical
-- record-level forms at every nesting level (raw-wire-form retention contract,
-- section C.6.5 — the exclusion is byte-region-scoped and transitive).
DedupMarshalledInstanceRecord ::= SEQUENCE {
    payloadBytes  OCTET STRING,
    schema        SchemaChainRef,
    payloadFormat UTF8String
}

-- Stream form of the P2 nested record (Appendix C section C.5.3; RATIFIED):
-- replaces the STD-008 section 16 SEQUENCE{schemaChainBytes, payloadBytes} at
-- P2 STREAM sites (nested @AtomicSerial fields, Any [20] arm bodies,
-- array/collection elements of @AtomicSerial type). Chain-first, matching the
-- section 16 field order. Same [8]-interior exclusion as above.
DedupNestedAtomicRecord ::= SEQUENCE {
    schema        SchemaChainRef,
    payloadBytes  OCTET STRING
}

END
